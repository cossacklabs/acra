-- Copyright 2020, Cossack Labs Limited
--
-- Licensed under the Apache License, Version 2.0 (the "License");
-- you may not use this file except in compliance with the License.
-- You may obtain a copy of the License at
--
-- http://www.apache.org/licenses/LICENSE-2.0
--
-- Unless required by applicable law or agreed to in writing, software
-- distributed under the License is distributed on an "AS IS" BASIS,
-- WITHOUT WARRANTIES OR CONDITIONS OF ANY KIND, either express or implied.
-- See the License for the specific language governing permissions and
-- limitations under the License.

-- ASN.1 grammar defining format of Acra Keystore, version 2.
--
-- Version 2 keystores are represented as hierarchy of key directories
-- usually stored in DER encoding as filsystem hierarchies.
--
-- Version 1 uses flat list of binary files to store each key individually.
-- The name of the file is ID of the key. There is no structure inside files:
-- each of them stores a single Themis private key.
AcraKeyStoreV2 DEFINITIONS IMPLICIT TAGS ::= BEGIN

-- Container for a signed object. Every exported object of the keystore
-- is packed into a SignedContainer for storage. For example, file-based
-- keystore keeps a file for each key directory. Every file contains
-- a SignedContainer with "contentType" equal to 'typeKeyDirectory'
-- and a KeyDirectory stored in its "data" field.
SignedContainer ::= SEQUENCE {
    payload     SEQUENCE {
        contentType     ContentType,    -- type of "data"
        version         INTEGER,        -- version number for "contentType"
        lastModified    UTCTime,        -- exporting timestamp
        data ANY DEFINED BY contentType -- actual signed payload
    },
    signatures  SET OF Signature        -- signatures for "payload"
}

-- Common content identifiers for the "data" field of SignedContainer objects.
ContentType ::= ENUMERATED {
    typeKeyRing             (1),
    typeKeyDirectory        (2),
    typeDirectKeyDirectory  (3),
    typeEncryptedKeys       (4)
--  ...
}

-- Signature for SignedContainer. A container can have multiple signatures
-- made with different algorithms, enabling future-proofing, extensibility,
-- and collision resistance. Signatures are computed for the "payload" of
-- SignedContainer, usually with HMAC keyed by the keystore master key.
-- The signing algorithm is indicated by the "algorithm" field.
Signature ::= SEQUENCE {
    algorithm   OBJECT IDENTIFIER,  -- signature algorithm
    signature   OCTET STRING        -- signature bytes
}

-- Key directory contains key rings and/or other key directories.
-- It has a name by which it can be referred to.
-- This is a compact variant of directory.
DirectKeyDirectory ::= SEQUENCE {
    name            LikelyUTF8String,   -- human-readable name of the directory
    keyRings    [1] SET OF KeyRing OPTIONAL,                -- attached key rings
    children    [2] SET OF DirectKeyDirectory OPTIONAL      -- child directories
}

-- Key directory contains key rings and/or other key directories.
-- It has a name by which it can be referred to.
-- This is a 'loose' variant of directory.
KeyDirectory ::= SEQUENCE {
    name            LikelyUTF8String,   -- human-readable name of the directory
    keyRings    [1] SET OF KeyRingReference OPTIONAL,       -- attached key rings
    children    [2] SET OF KeyDirectoryReference OPTIONAL   -- child directories
}

-- Encrypted set of key rings, typically used for backup purposes or to transfer
-- keys between machines. SignedContainer actually contains an OCTET STRING with
-- DER serialization of this object encrypted with Themis Secure Cell.
EncryptedKeys := SEQUENCE {
    keyRings    SET OF KeyRing     -- exported key ring data
}

-- Reference to a child key ring, not included into KeyDirectory object directly.
-- However it can be located in some external memory using its name and the current
-- directory path. Signatures are also provided for integrity validation.
-- The key ring should be packed in SignedContainer.
KeyRingReference ::= SEQUENCE {
    purpose     LikelyUTF8String,   -- human-readable purpose of the key ring
    signatures  SET OF Signature    -- signatures for key ring
}

-- Reference to a child subdirectory, not included into KeyDirectory object
-- directly. However it can be located in some external memory using its
-- name and the current directory path. Signature are also provided for
-- integrity validation. The directory should be packed in SignedContainer.
KeyDirectoryReference ::= SEQUENCE {
    name        LikelyUTF8String,   -- human-readable name of the directory
    signatures  SET OF Signature    -- signatures for directory
}

-- Key ring holds multiple versions of a key used for the same purpose. Keys
-- are usually ordered from oldest to newest, with new keys added to the back
-- of the sequence. One key in a key ring may be designated as 'current'.
KeyRing ::= SEQUENCE {
    purpose     LikelyUTF8String,   -- human-readable purpose of the key ring
    keys        SEQUENCE OF Key,    -- keys that form this key ring
    current     INTEGER             -- seqnum of current key (-1 if none)
}

-- Cryptographic key stored in the keystore. The key is identified by its
-- content and can have multiple representations. It also has some metadata
-- pertaining to its usage restrictions.
Key ::= SEQUENCE {
    seqnum      INTEGER,        -- sequence number of the key in key ring
    state       KeyState,       -- current state of the key
    validSince  UTCTime,        -- cryptoperiod of the key
    validUntil  UTCTime,
    data        SET OF KeyData  -- key material, by format
}

-- State of the key. See NIST SP 800-57.
KeyState ::= ENUMERATED {
    keyPreActive    (1),    -- initial state of newly created key
    keyActive       (2),    -- key is in active use
    keySuspended    (3),    -- active use temporarily suspended
    keyDeactivated  (4),    -- active use period permanently ended
    keyCompromised  (5),    -- key is suspected to be compromised
    keyDestroyed    (6)     -- key material has been destroyed
}

-- Key material in a particular format.
KeyData ::= SEQUENCE {
    format              KeyFormat,  -- defines which fields are required
    publicKey       [1] PublicKey OPTIONAL,
    privateKey      [2] PrivateKey OPTIONAL,
    symmetricKey    [3] SymmetricKey OPTIONAL
--  ...
}

KeyFormat ::= ENUMERATED {
    themisKeyPair       (1),    -- asymmetric key pair (public and private key, or public key alone)
--  reserved            (2),    -- (was intended for standalone public keys, now reserved)
    themisSymmetricKey  (3)     -- symmetric key
--  ...
}

-- Generic public key. Stored in plaintext.
PublicKey ::= OCTET STRING

-- Generic private key. Stored encrypted.
PrivateKey ::= OCTET STRING

-- Generic symmetric key. Stored encrypted.
SymmetricKey ::= OCTET STRING

-- We expect human-readable UTF-8 here, but actually allow arbitrary bytes.
LikelyUTF8String ::= OCTET STRING

END -- AcraKeyStoreV2 DEFINITIONS
